[DOCUMENT, TITLE: Jaso Requirements]
[GRAMMAR]
ELEMENTS:
- DOCUMENT:
    REQ_LINKS:
    - role: Parent
      rule: "refers-to-document(DOCUMENT)"
    - role: Child
      rule: "is-child-of(DOCUMENT)"
- REQUIREMENT:
    REQ_LINKS:
    - role: Refines
      rule: "refines(REQUIREMENT)"
    - role: Relates
      rule: "relates-to(REQUIREMENT)"
- SECTION

[SECTION, TITLE: Overview]
[REQUIREMENT, ID: REQ-JASO-001, TITLE: Core Functionality]
STATEMENT:
The system, named Jaso, shall read jazz standards specified in MusicXML or LilyPond format, and generate guitar tablature for the melody and an optimized chord progression.

RATIONALE:
To provide musicians with an easy-to-play arrangement of jazz standards, minimizing difficult fingering transitions.
[/REQUIREMENT]
[/SECTION]

[SECTION, TITLE: Input Formats]
[REQUIREMENT, ID: REQ-JASO-002, TITLE: Score Input Formats]
STATEMENT:
The system shall accept files in MusicXML format (.musicxml, .xml, .mxl) or LilyPond format (.ly) as input for the musical piece.
It must parse:
1. The melody line, including notes and rhythms.
2. The chord symbols and their exact `.offset` start times.
3. Lyrics and Rehearsal Marks (song sections), if available.

COMMENT:
We will use the music21 library to extract the musical information and specific object properties accurately.
[/REQUIREMENT]

[REQUIREMENT, ID: REQ-JASO-003, TITLE: Musical Logic and Shape Input]
STATEMENT:
The system shall load a library of possible chord shapes (voicings) and instrument-specific tuning/normalization data from JSON files.
Each entry in the chord JSON file should define:
1. The chord name (e.g., "Cmaj7", "G7b9").
2. A list of possible fingerings (voicings) for that chord.
3. Each voicing specifying relative fret positions and a string root.
4. Instrument-specific configuration (`instrument_[name].json`) defining open string MIDI, string order, and enharmonic equivalents.

RATIONALE:
To support any stringed instrument and ensure a flexible, data-driven approach to musical logic and fingering calculations.
[/REQUIREMENT]
[/SECTION]

[SECTION, TITLE: Core Logic]
[REQUIREMENT, ID: REQ-JASO-004, TITLE: Ease of Playing Metric]
STATEMENT:
The system shall define and use a metric to quantify the "ease of playing" between two consecutive chords. This metric should be based on minimizing the total fret-hand movement required.

COMMENT:
The primary cost function will be the sum of the fret distances that each finger has to travel between the end of the first chord and the start of the second chord. Other factors like barring or finger reuse could be considered in later versions.
[/REQUIREMENT]

[REQUIREMENT, ID: REQ-JASO-005, TITLE: Optimal Chord Progression Algorithm]
STATEMENT:
Given a sequence of chord symbols from the MusicXML file, the system shall use the "ease of playing" metric to find the sequence of chord voicings from the JSON library that has the lowest total transition cost.

RATIONALE:
This is the core optimization problem. An algorithm like Viterbi or another dynamic programming approach is likely suitable here to find the "path of least resistance" through the possible voicings.
[/REQUIREMENT]

[REQUIREMENT, ID: REQ-JASO-009, TITLE: Smart Melody Optimization]
STATEMENT:
The system shall calculate the optimal sequence of string/fret positions for the melody line using a Viterbi search that minimizes the total distance (fret and string jumps) between consecutive notes.

RATIONALE:
To prevent the melody lead line from jumping wildly across the fretboard and ensure it remains in a playable "position" or "box" consistent with the ease-of-play metric.
[/REQUIREMENT]

[REQUIREMENT, ID: REQ-JASO-006, TITLE: Playing Style Substitutions]
STATEMENT:
The system shall apply style-specific chord substitutions when standard jazz flavors are selected, governed by the `substitutions_[flavor].json` matrices:
1. For Gypsy Jazz (`gypsy`): The system shall substitute generic "Minor" and "Minor 7" chords with "Minor 6" to reflect the genre's characteristic diminished sound.
2. For Freddie Green (`freddie`): The system shall simplify "Minor 7" to "Minor" (due to omitted 5ths), and substitute "Dominant 7" chords with "Minor 7" chords rooted a perfect fifth higher to create smooth voice leading.

RATIONALE:
By defining mapping matrices, the system can automatically resolve generic MusicXML chords into authentic genre-specific simplifications before passing them to the optimization algorithm, preserving historical playing traditions without requiring manual user edits.
[/REQUIREMENT]

[REQUIREMENT, ID: REQ-JASO-010, TITLE: Instrument Decoupling]
STATEMENT:
The system shall be decoupled from guitar-specific hard-coding. It shall determine string availability, tuning, and note-to-fret mapping by loading an `instrument_[type].json` profile.

RATIONALE:
To allow the tool to generate arrangements for other stringed instruments (Ukulele, Banjo, etc.) or alternative guitar tunings (DADGAD, Open G) without code modification.
[/REQUIREMENT]

[REQUIREMENT, ID: REQ-JASO-011, TITLE: Application Configuration]
STATEMENT:
The system shall externalize all layout constants (beats per measure, measures per line, CPQN) and optimizer cost weights (fret distance penalties, string jump weights) into an `app_config.json` file.

RATIONALE:
To provide users with control over the visual presentation and the "playing style" logic of the optimization engine.
[/REQUIREMENT]
[/SECTION]

[SECTION, TITLE: Output]
[REQUIREMENT, ID: REQ-JASO-007, TITLE: Tablature Generation]
STATEMENT:
The system shall generate a single output file containing:
1. A "Dual-Staff" layout where Accompaniment (Chords) and Lead (Melody) are rendered in separate, vertically aligned 6-string grids.
2. The tablature grids must reflect a configurable rhythmic resolution spacing (CPQN) separated by explicit standard measure bars (|).
3. The number of measures per line and beats per measure shall be configurable via the application settings.
4. Parsed song section markers rendered above the accompaniment measures, and parsed lyrics printed below the Lead staff.

RATIONALE:
Providing a dual-staff layout ensures clarity between the rhythm and lead parts while maintaining a synchronized rhythmic timeline for practice.
[/REQUIREMENT]
[REQUIREMENT, ID: REQ-JASO-012, TITLE: MusicXML Export]
STATEMENT:
The system shall optionally export the optimized arrangement back into a valid MusicXML file.
1. The exported file must contain two synchronized parts: the original Melody (P1) and the generated Chord Accompaniment (P2).
2. The accompaniment part must use explicit `<chord/>` elements to ensure MuseScore groups the notes into a single voice.
3. The system must inject `<technical>` tags (string and fret numbers) onto the chord notes matching the optimizer's selected voicings.
4. The system must inject `<staff-details>` and `<staff-tuning>` elements to ensure the accompaniment part is correctly interpreted as standard 6-string guitar tablature by notation software like MuseScore.
5. All measure lengths, including pickup measures (anacrusis), must align exactly between the melody and accompaniment parts without introducing tied notes across measure boundaries.

RATIONALE:
To allow users to view, playback, and print the optimized tablature using standard notation software alongside the text-based output.
[/REQUIREMENT]
[/SECTION]

[SECTION, TITLE: Non-Functional Requirements]
[REQUIREMENT, ID: REQ-JASO-008, TITLE: Command-Line Interface]
STATEMENT:
The system shall be executable as a Python script from the command line.
It should accept arguments for:
1. The input score file path (MusicXML or LilyPond).
2. The output tablature text file path.
3. An optional `--flavor` argument to select the style of chord voicings (e.g., classical, freddie, gypsy).
4. An optional `--xml` argument to specify the output path for the optimized MusicXML file.
5. Backward compatibility allowing an explicit JSON chords file to be passed instead of a flavor.
[/REQUIREMENT]
[/SECTION]
[/DOCUMENT]
